--
-- HUAWEI-VBST-MIB.my
-- MIB generated by MG-SOFT Visual MIB Builder Version 3.0 Build 253
-- Monday, March 13, 2017 at 21:02:38
--

--  HUAWEI-VBST-MIB.mib
-- MIB generated by MG-SOFT Visual MIB Builder Version 4.0 Build 347
-- Thursday, February 16, 2017 at 03:06:08
-- 
--  =================================================================
-- Copyright (C) 2023 by HUAWEI TECHNOLOGIES. All rights reserved
-- 
-- Description: VBST huawei mib define
-- Reference: VBST 
-- Version: V1.06
-- History:
--    <zongchao 00240494>,<2013.09.29>,<create>
-- =================================================================

	HUAWEI-VBST-MIB DEFINITIONS ::= BEGIN
 
		IMPORTS
			entPhysicalName			
				FROM ENTITY-MIB			
			hwDatacomm			
				FROM HUAWEI-MIB			
			OBJECT-GROUP, MODULE-COMPLIANCE, NOTIFICATION-GROUP			
				FROM SNMPv2-CONF			
			Integer32, OBJECT-TYPE, MODULE-IDENTITY, NOTIFICATION-TYPE			
				FROM SNMPv2-SMI;
	
	
--  1.3.6.1.4.1.2011.5.25.323
-- November 18, 2015 at 14:10 GMT
-- February 16, 2017 at 03:05 GMT
-- August 11, 2010 at 16:00 GMT
-- November 18, 2015 at 14:10 GMT
		hwVbstMIB MODULE-IDENTITY 
			LAST-UPDATED "202308071124Z"
			ORGANIZATION 
				"Huawei Technologies Co.,Ltd."
			CONTACT-INFO 
				"Huawei Industrial Base
				Bantian, Longgang
				Shenzhen 518129
				People's Republic of China
				Website: http://www.huawei.com
				Email: support@huawei.com
				"
  
			DESCRIPTION 
				"Please provide the descritpion."
                       
			REVISION "202308071124Z"		-- July 12, 2023 at 11:22 GMT
			DESCRIPTION
				"V1.06, Updated to include BPDU rate."

			REVISION "202307121116Z"		-- July 12, 2023 at 11:22 GMT
			DESCRIPTION
				"V1.05, Updated to include PV suppression."

                        REVISION "201807040000Z"		-- July 04, 2018 at 03:05 GMT
                        DESCRIPTION 
				"V1.04, Updated to include support for VBST."

                        REVISION "201703140305Z"		-- March 14, 2017 at 03:05 GMT
			DESCRIPTION
				"V1.03, Updated to include support for VBST."

			REVISION "201702160305Z"		-- February 16, 2017 at 03:05 GMT
			DESCRIPTION
				"V1.02, Updated to include support for VBST."

			REVISION "201511181410Z"		-- November 18, 2015 at 14:10 GMT
			DESCRIPTION
				"V1.01, Updated to include support for VBST."
			REVISION "201008111600Z"		-- August 11, 2010 at 16:00 GMT
			DESCRIPTION
				"V1.00, initial version."
			::= { hwDatacomm 323 }
		
	
	
--
-- Node definitions
--
	
--  Node definitions
-- 
-- Top-level structure of the MIB
-- 1.3.6.1.4.1.2011.5.25.323.1
		-- 1.3.6.1.4.1.2011.5.25.323.1
		hwVbstObjects OBJECT IDENTIFIER ::= { hwVbstMIB 1 }
		
--  MIB Objects
-- 1.3.6.1.4.1.2011.5.25.323.1.1
		-- 1.3.6.1.4.1.2011.5.25.323.1.1
		hwVbstMaxTrunkNum OBJECT-TYPE
			SYNTAX Integer32 (0..65535)
			MAX-ACCESS accessible-for-notify
			STATUS current
			DESCRIPTION
				"The max number of the Eth-Trunk port."
			::= { hwVbstObjects 1 }
		
--  1.3.6.1.4.1.2011.5.25.323.1.2
		-- 1.3.6.1.4.1.2011.5.25.323.1.2
		hwVbstMaxPVNum OBJECT-TYPE
			SYNTAX Integer32 (0..65535)
			MAX-ACCESS accessible-for-notify
			STATUS current
			DESCRIPTION
				"The max number of the Port-Vlan."
			::= { hwVbstObjects 2 }
		
--  1.3.6.1.4.1.2011.5.25.323.1.3
		-- 1.3.6.1.4.1.2011.5.25.323.1.3
		hwVbstMaxVlanNum OBJECT-TYPE
			SYNTAX Integer32 (0..65535)
			MAX-ACCESS accessible-for-notify
			STATUS current
			DESCRIPTION
				"The max number of VLANs running VBST."
			::= { hwVbstObjects 3 }
		
--  1.3.6.1.4.1.2011.5.25.323.1.4
		-- 1.3.6.1.4.1.2011.5.25.323.1.4
		hwVbstVlanNum OBJECT-TYPE
			SYNTAX Integer32
			MAX-ACCESS accessible-for-notify
			STATUS current
			DESCRIPTION
				"Number of VLANs that cannot be calculated in the VBST packets received by interface."
			::= { hwVbstObjects 4 }
		
--  1.3.6.1.4.1.2011.5.25.323.1.5
		-- 1.3.6.1.4.1.2011.5.25.323.1.5
		hwVbstTrapPort OBJECT-TYPE
			SYNTAX OCTET STRING
			MAX-ACCESS accessible-for-notify
			STATUS current
			DESCRIPTION
				"Interfaces where the VBST packets containing the VLANs that cannot be calculated are received."
			::= { hwVbstObjects 5 }
		
--  1.3.6.1.4.1.2011.5.25.323.1.6
		-- 1.3.6.1.4.1.2011.5.25.323.1.6
		hwVbstTrapVlan OBJECT-TYPE
			SYNTAX OCTET STRING
			MAX-ACCESS accessible-for-notify
			STATUS current
			DESCRIPTION
				"Number of VLAN lists that cannot be calculated in the VBST packets received by interface."
			::= { hwVbstObjects 6 }
		
		-- 1.3.6.1.4.1.2011.5.25.323.1.7
		hwVbstMaxTrunkPVNum OBJECT-TYPE
			SYNTAX Integer32
			MAX-ACCESS accessible-for-notify
			STATUS current
			DESCRIPTION
				"Number of Eth-Trunk Port VLANs with VBST enabled."
			::= { hwVbstObjects 7 }

                                       -- 1.3.6.1.4.1.2011.5.25.323.1.8
		hwVbstConflictDescription OBJECT-TYPE
			SYNTAX OCTET STRING
			MAX-ACCESS accessible-for-notify
			STATUS current
			DESCRIPTION
				"The specific cause of the configuration conflict with the remote observing port configuration."
			::= { hwVbstObjects 8 }
	
                                       -- 1.3.6.1.4.1.2011.5.25.323.1.9
		hwVbstPVSuppressThreshold  OBJECT-TYPE
			SYNTAX      Integer32 (0..65535)
			MAX-ACCESS  accessible-for-notify
			STATUS      current
			DESCRIPTION
				"the PV suppression threshold of the VBST."
			::= { hwVbstObjects 9 }

                                       -- 1.3.6.1.4.1.2011.5.25.323.1.10
		hwVbstCurrentPv  OBJECT-TYPE
			SYNTAX      Integer32 (0..65535)
			MAX-ACCESS  accessible-for-notify
			STATUS      current
			DESCRIPTION
				"Number of PVs currently used by VBST (The number of PVs occupied by the peer-link interface used during M-LAG establishment is not counted)."
			::= { hwVbstObjects 10 }

                                       -- 1.3.6.1.4.1.2011.5.25.323.1.11
		hwVbstRateThreshold  OBJECT-TYPE
			SYNTAX      Integer32 (0..65535)
			MAX-ACCESS  accessible-for-notify
			STATUS      current
			DESCRIPTION
				"Threshold for the rate at which VBST sends BPDUs."
			::= { hwVbstObjects 11 }

                                       -- 1.3.6.1.4.1.2011.5.25.323.1.12
		hwVbstCurrentRate  OBJECT-TYPE
			SYNTAX      Integer32 (0..65535)
			MAX-ACCESS  accessible-for-notify
			STATUS      current
			DESCRIPTION
				"Indicates the current rate at which VBST sends BPDUs."
			::= { hwVbstObjects 12 }

--  1.3.6.1.4.1.2011.5.25.323.2
		-- 1.3.6.1.4.1.2011.5.25.323.2
		hwVbstNotifications OBJECT IDENTIFIER ::= { hwVbstMIB 2 }
		
--   Notifications
-- 1.3.6.1.4.1.2011.5.25.323.2.1
		-- 1.3.6.1.4.1.2011.5.25.323.2.1
		hwVbstTrunkNumExceeded NOTIFICATION-TYPE
			OBJECTS { hwVbstMaxTrunkNum }
			STATUS current
			DESCRIPTION 
				"Trap message is generated by VBST node when 
				it detects that number of trunk ports has exceeded the specification limit."
			::= { hwVbstNotifications 1 }
		
--  1.3.6.1.4.1.2011.5.25.323.2.2
		-- 1.3.6.1.4.1.2011.5.25.323.2.2
		hwVbstTrunkNumResumed NOTIFICATION-TYPE
			OBJECTS { hwVbstMaxTrunkNum }
			STATUS current
			DESCRIPTION 
				"Trap message is generated by VBST node when 
				it detects that the number of trunk ports has resumed below 95% of the specification limit."
			::= { hwVbstNotifications 2 }
		
--  1.3.6.1.4.1.2011.5.25.323.2.3
		-- 1.3.6.1.4.1.2011.5.25.323.2.3
		hwVbstPVNumExceeded NOTIFICATION-TYPE
			OBJECTS { entPhysicalName, hwVbstMaxPVNum }
			STATUS current
			DESCRIPTION 
				"Trap message is generated by VBST node when 
				it detects that the number of PortVlan has exceeded the specification limit."
			::= { hwVbstNotifications 3 }
		
--  1.3.6.1.4.1.2011.5.25.323.2.4
		-- 1.3.6.1.4.1.2011.5.25.323.2.4
		hwVbstPVNumResumed NOTIFICATION-TYPE
			OBJECTS { entPhysicalName, hwVbstMaxPVNum }
			STATUS current
			DESCRIPTION 
				"Trap message is generated by VBST node when 
				it detects that the number of PortVlan has resumed below 95% of the specification limit."
			::= { hwVbstNotifications 4 }
		
--  1.3.6.1.4.1.2011.5.25.323.2.5
		-- 1.3.6.1.4.1.2011.5.25.323.2.5
		hwVbstVlanNumExceeded NOTIFICATION-TYPE
			OBJECTS { hwVbstMaxVlanNum }
			STATUS current
			DESCRIPTION 
				"Trap message is generated by VBST node when 
				it detects that the number of VLANs running VBST has exceeded the specification limit."
			::= { hwVbstNotifications 5 }
		
--  1.3.6.1.4.1.2011.5.25.323.2.6
		-- 1.3.6.1.4.1.2011.5.25.323.2.6
		hwVbstVlanNumResumed NOTIFICATION-TYPE
			OBJECTS { hwVbstMaxVlanNum }
			STATUS current
			DESCRIPTION 
				"Trap message is generated by VBST node when 
				it detects that the number of VLANs running VBST has resumed below 95% of the specification limit."
			::= { hwVbstNotifications 6 }
		
--  1.3.6.1.4.1.2011.5.25.323.2.7
		-- 1.3.6.1.4.1.2011.5.25.323.2.7
		hwVbstInvalidPV NOTIFICATION-TYPE
			OBJECTS { hwVbstVlanNum, hwVbstTrapPort, hwVbstTrapVlan }
			STATUS current
			DESCRIPTION 
				"Trap message is generated by VBST node when 
				it detects that the number of VLANs that cannot be calculated in the VBST packets received by interface exceeds the threshold. "
			::= { hwVbstNotifications 7 }
		
		-- 1.3.6.1.4.1.2011.5.25.323.2.8
		hwVbstTrunkPVNumExceeded NOTIFICATION-TYPE
			OBJECTS { hwVbstMaxTrunkPVNum }
			STATUS current
			DESCRIPTION 
				"Trap message is generated by VBST node when 
				it detects that the number of VLANs on all Eth-Trunks exceeds the limit of VBST."
			::= { hwVbstNotifications 8 }
		
		-- 1.3.6.1.4.1.2011.5.25.323.2.9
		hwVbstTrunkPVNumResumed NOTIFICATION-TYPE
			OBJECTS { hwVbstMaxTrunkPVNum }
			STATUS current
			DESCRIPTION 
				"Trap message is generated by VBST node when 
				it detects the number of VLANs on all Eth-Trunks falls below the limit of VBST."
			::= { hwVbstNotifications 9 }

                                       -- 1.3.6.1.4.1.2011.5.25.323.2.10
		hwVbstRspanCfgConflict NOTIFICATION-TYPE
			OBJECTS { hwVbstConflictDescription }
			STATUS current
			DESCRIPTION 
				"In VBST mode, the Eth-Trunk configuration conflicts with the remote observing port configuration."
			::= { hwVbstNotifications 10 }
		
		-- 1.3.6.1.4.1.2011.5.25.323.2.11
		hwVbstPVSuppressed NOTIFICATION-TYPE
			OBJECTS { hwVbstPVSuppressThreshold, hwVbstCurrentPv, hwVbstRateThreshold, hwVbstCurrentRate }
			STATUS current
			DESCRIPTION 
				"Trap message is generated by VBST node when 
				it detects that the number of PortVlan has exceeded the suppression threshold."
			::= { hwVbstNotifications 11 }

		-- 1.3.6.1.4.1.2011.5.25.323.2.12
		hwVbstPVSuppressResumed NOTIFICATION-TYPE
			OBJECTS { hwVbstPVSuppressThreshold, hwVbstCurrentPv, hwVbstRateThreshold, hwVbstCurrentRate }
			STATUS current
			DESCRIPTION 
				"Trap message is generated by VBST node when 
				it detects that the number of PortVlan has resumed below the suppression threshold."
			::= { hwVbstNotifications 12 }

		-- 1.3.6.1.4.1.2011.5.25.323.2.13
		hwVbstBpduRateExceeded NOTIFICATION-TYPE
			OBJECTS { hwVbstRateThreshold, hwVbstCurrentRate }
			STATUS current
			DESCRIPTION 
				"Trap message is generated by VBST node when 
				it detects that the rate at which VBST sends BPDUs exceeds the upper limit."
			::= { hwVbstNotifications 13 }

		-- 1.3.6.1.4.1.2011.5.25.323.2.14
		hwVbstBpduRateResumed NOTIFICATION-TYPE
			OBJECTS { hwVbstRateThreshold, hwVbstCurrentRate }
			STATUS current
			DESCRIPTION 
				"Trap message is generated by VBST node when 
				it detects that the rate at which VBST sends BPDUs has restored to normal range."
			::= { hwVbstNotifications 14 }

--  1.3.6.1.4.1.2011.5.25.323.3
		-- 1.3.6.1.4.1.2011.5.25.323.3
		hwVbstConformance OBJECT IDENTIFIER ::= { hwVbstMIB 3 }
		
--   Conformance
-- 1.3.6.1.4.1.2011.5.25.323.3.1
		-- 1.3.6.1.4.1.2011.5.25.323.3.1
		hwVbstGroups OBJECT IDENTIFIER ::= { hwVbstConformance 1 }
		
--  1.3.6.1.4.1.2011.5.25.323.3.1.1
		-- 1.3.6.1.4.1.2011.5.25.323.3.1.1
		hwVbstObjectGroup OBJECT-GROUP
			OBJECTS { hwVbstMaxTrunkNum, hwVbstMaxPVNum, hwVbstMaxVlanNum, hwVbstVlanNum, hwVbstTrapPort, 
				hwVbstTrapVlan, hwVbstMaxTrunkPVNum,  hwVbstConflictDescription, hwVbstPVSuppressThreshold,
                               hwVbstCurrentPv, hwVbstRateThreshold, hwVbstCurrentRate  }
			STATUS current
			DESCRIPTION 
				"The object group."
			::= { hwVbstGroups 1 }
		
--  1.3.6.1.4.1.2011.5.25.323.3.1.2
		-- 1.3.6.1.4.1.2011.5.25.323.3.1.2
		hwVbstNotificationGroup NOTIFICATION-GROUP
			NOTIFICATIONS { hwVbstTrunkNumExceeded, hwVbstTrunkNumResumed, hwVbstPVNumExceeded, hwVbstPVNumResumed, hwVbstVlanNumExceeded, 
				hwVbstVlanNumResumed, hwVbstInvalidPV, hwVbstTrunkPVNumExceeded, hwVbstTrunkPVNumResumed, hwVbstRspanCfgConflict,
				hwVbstPVSuppressed, hwVbstPVSuppressResumed, hwVbstBpduRateExceeded, hwVbstBpduRateResumed }
			STATUS current
			DESCRIPTION 
				"The notification group."
			::= { hwVbstGroups 2 }
		
--  1.3.6.1.4.1.2011.5.25.323.3.2
		-- 1.3.6.1.4.1.2011.5.25.323.3.2
		hwVbstCompliances OBJECT IDENTIFIER ::= { hwVbstConformance 2 }
		
--   this module
-- 1.3.6.1.4.1.2011.5.25.323.3.2.1
-- this module
		-- 1.3.6.1.4.1.2011.5.25.323.3.2.1
		hwVbstCompliance MODULE-COMPLIANCE
			STATUS current
			DESCRIPTION 
				"The core compliance statement for all implementations."
			MODULE -- this module
				MANDATORY-GROUPS { hwVbstObjectGroup, hwVbstNotificationGroup }
			::= { hwVbstCompliances 1 }
		
	
	END

--
-- HUAWEI-VBST-MIB.my
--
